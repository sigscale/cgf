ExposureFunctionAPIChargingDataTypes {itu-t (0) identified-organization (4) etsi (0) mobileDomain (0) charging (5) exposureFunctionAPIChargingDataTypes (14) asn1Module (0) version2 (1)}

DEFINITIONS IMPLICIT TAGS  ::= BEGIN

	-- EXPORTS everything

	IMPORTS
		DiameterIdentity,
		IPAddress,
		LocalSequenceNumber,
		ManagementExtensions,
		MSTimeZone,
		NodeID,
		RecordType,
		SCSASAddress,
		ServiceContextID,
		SubscriptionID,
		TimeStamp
	FROM GenericChargingDataTypes {itu-t (0) identified-organization (4) etsi(0) mobileDomain (0) charging (5) genericChargingDataTypes (0) asn1Module (0) version2 (1)};

	--
	-- ExposureFunctionAPI RECORDS
	--

	ExposureFunctionAPIRecordType ::= CHOICE
	--
	-- Record values 120 are ExposureFunctionAPI specific
	--
	{
		eASCERecord  [120] EASCERecord    
	}

	EASCERecord  ::= SET
	{
		recordType                  [0] RecordType,
		retransmission              [1] NULL OPTIONAL,
		serviceContextID            [2] ServiceContextID OPTIONAL,
		nodeId                      [3] NodeID OPTIONAL,
		sCEFID                      [4] DiameterIdentity OPTIONAL,
		sCEFAddress                 [5] IPAddress OPTIONAL,
		aPIIdentifier               [6] OCTET STRING OPTIONAL,
		tLTRI                       [7] INTEGER OPTIONAL,
		sCSASAddress                [9] SCSASAddress OPTIONAL,
		eventTimestamp             [10] TimeStamp OPTIONAL,
		aPIInvocationTimestamp     [11] TimeStamp OPTIONAL,
		aPIDirection               [12] APIDirection OPTIONAL,
		aPINetworkServiceNode      [13] APINetworkServiceNode OPTIONAL,
		aPIContent                 [14] UTF8String OPTIONAL,
		aPISize                    [15] INTEGER OPTIONAL,
		aPIresultCode              [16] INTEGER OPTIONAL,
		externalIdentifier         [17] SubscriptionID OPTIONAL,
		localRecordSequenceNumber  [18] LocalSequenceNumber OPTIONAL,
		recordExtensions           [19] ManagementExtensions OPTIONAL,
		startTime                  [20] TimeStamp OPTIONAL,
		stopTime                   [21] TimeStamp OPTIONAL,
		...
	}

	--
	-- ExposureFunctionAPI DATA TYPES
	--
	--
	-- A
	--

	APIDirection ::= ENUMERATED
	--
	-- Used for distinguish the API invocation or API notification
	--
	{
		invocation    (0),
		notification  (1)
	}

	APINetworkServiceNode ::= ENUMERATED
	{
		mME    (0),
		sGSN   (1),
		hSS    (2),
		pCRF   (3),
		pFDF   (4),
		bMSC   (5),
		cCSCF  (6),
		rCAF   (7)
	}



END
